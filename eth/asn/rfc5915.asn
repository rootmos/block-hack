ECPrivateKey { iso(1) identified-organization(3) dod(6)
  internet(1) security(5) mechanisms(5) pkix(7) id-mod(0)
  id-mod-ecprivateKey(65) }

DEFINITIONS EXPLICIT TAGS ::=

BEGIN

-- EXPORTS ALL;

IMPORTS

-- FROM New PKIX ASN.1 [RFC5912]

EcpkParameters, namedCurve
  FROM PKIX1Algorithms88 
    { iso(1) identified-organization(3) dod(6) internet(1)
      security(5) mechanisms(5) pkix(7) id-mod(0)
      id-mod-pkix1-algorithms(17) }

;

ECPrivateKey ::= SEQUENCE {
  version        INTEGER { ecPrivkeyVer1(1) } (ecPrivkeyVer1),
  privateKey     OCTET STRING,
  parameters [0] EcpkParameters {{ namedCurve }} OPTIONAL,
  publicKey  [1] BIT STRING OPTIONAL
}

END
